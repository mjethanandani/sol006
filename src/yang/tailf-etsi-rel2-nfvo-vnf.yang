submodule tailf-etsi-rel2-nfvo-vnf {
  belongs-to tailf-etsi-rel2-nfvo {
    prefix nfvo-rel2;
  }

  import ietf-inet-types {
    prefix inet;
  }
  import ietf-yang-types {
    prefix yang;
  }
  include tailf-etsi-rel2-nfvo-common;

  description
    "Models for VNFD according to GS NFV-IFA 011.";

  revision 2018-04-24 {
    description
      "Initial revision.

       Common data structure to support VNFD according to:
       ETSI GS NFV-IFA 011 V2.1.1 (2016-10)";

    reference
      "ETSI GS NFV-IFA 011 V2.1.1 (2016-10)";
  }

  grouping cpd {
    description
      "A Cpd information element describes network connectivity to a
       compute resource or a VL.";
    reference
      "GS NFC IFA011: Section 7.1.6.3 Cpd Information Element";
    leaf id {
      type string;
      description
        "Identifier of this Cpd information element.";
      reference
        "GS NFV IFA011: Section 7.1.6.3, Cpd information element.";
    }
    leaf layer-protocol {
      mandatory true;
      type identityref {
        base layer-protocol;
      }
      description
        "Identifies which protocol the CP uses for connectivity
         purposes (Ethernet, MPLS, ODU2, IPV4, IPV6, Pseudo-Wire,
         etc.).";
      reference
        "GS NFV IFA011: Section 7.1.6.3, Cpd information element.";
    }
    leaf role {
      type cp-role;
      description
        "Identifies the role of the port in the context of the
         traffic flow patterns in the VNF or parent NS. For example a
         VNF with a tree flow pattern within the VNF will have legal
         cpRoles of ROOT and LEAF.";
      reference
        "GS NFV IFA011: Section 7.1.6.3, Cpd information element.";
    }
    leaf description {
      type string;
      description
        "Human readable description of the connection point";
      reference
        "GS NFV IFA011: Section 7.1.6.3, Cpd information element.";
    }
    list address-data {
      key "address-type";
      leaf address-type {
        type enumeration {
          enum mac-address;
          enum ip-address;
        }
        description
          "Describes the type of the address to be assigned to the CP 
           instantiated from the parent CPD.
           Value:
           • MAC address.
           • IP address.
           • …
           The content type shall be aligned with the address type 
           supported by the layerProtocol attribute of the parent CPD.";
        reference
          "GS NFV IFA011: Section 7.1.3.3, AddressData information
           element.";
      }
      container l2-address-data {
        when "../nfvo-rel2:address-type='mac-address'";
      }
      container l3-address-data {
        when "../nfvo-rel2:address-type='ip-address'";
        leaf ip-address-assignment {
          type boolean;
          description
            "Specify if the address assignment is the responsibility
             of management and orchestration function or not. If it
             is set to True, it is the management and orchestration
             function responsibility. ";
          reference
            "GS NFV IFA011: Section 7.1.3.4, L3AddressData 
             information element.";
        }
        leaf floating-ip-activated {
          type boolean;
          description
            "Specify if the floating IP scheme is activated on the CP
             or not.";
          reference
            "GS NFV IFA011: Section 7.1.3.4, L3AddressData 
             information element.";
        }
        leaf ip-address-type {
          type enumeration {
            enum "ipv4";
            enum "ipv6";
          }
          description
            "Define address type. The address type should be aligned
             with the address type supported by the layerProtocol
             attribute of the parent VnfExtCpd.";
          reference
            "GS NFV IFA011: Section 7.1.3.4, L3AddressData 
             information element.";
        }
        leaf number-of-ip-addresses {
          type uint32;
          description
            "Minimum number of IP addresses to be assigned based on
             this L3AddressData information element.";
          reference
            "GS NFV IFA011: Section 7.1.3.4, L3AddressData 
             information element.";
        }
      }
      description
        "The AddressData information element supports providing
         information about the addressing scheme and parameters
         applicable to a CP.";
      reference
        "GS NFV IFA011: Section 7.1.3.3, AddressData information
         element.";
    }
  }

  grouping virtual-network-interface-requirement {
    list virtual-network-interface-requirement {
      key "name";
      leaf name {
        type string;
        description
          "Provides a human readable name for the requirement.";
        reference
          "GS NFV-IFA011: Section 7.1.6.6,
           VirtualNetworkInterfaceRequirements information element";
      }
      leaf description {
        type string;
        description
          "Provides a human readable description of the requirement.";
        reference
          "GS NFV-IFA011: Section 7.1.6.6,
           VirtualNetworkInterfaceRequirements information element";
      }
      leaf support-mandatory {
        type boolean;
        description
          "Indicates whether fulfilling the constraint is
           mandatory (true) for successful operation or desirable
           (false).";
        reference
          "GS NFV-IFA011: Section 7.1.6.6,
           VirtualNetworkInterfaceRequirements information element";
       }
      leaf requirement {
        mandatory true;
        type enumeration {
          enum "SR-IOV";
          enum "DPDK";
        }
        description
          "Specifies a requirement such as the support of SR-IOV, a
           particular data plane acceleration library, an API to be
           exposed by a NIC, etc.";
        reference
          "GS NFV-IFA011: Section 7.1.6.6,
           VirtualNetworkInterfaceRequirements information element";
      }
    }
  }

  grouping vnfd {
    list vnfd {
      key "id";
      description
        "A VNF Descriptor (VNFD) is a deployment template which
         describes a VNF in terms of deployment and operational 
         behaviour requirements. It also contains connectivity,
         interface and virtualised resource requirements";
      reference
        "GS NFV-IFA011: Section 7.1.2, VNFD information element";
      leaf id {
        type string;
        description
          "Identifier of this VNFD information element. This attribute
           shall be globally unique. The format will be defined in the
           data model specification phase.";
        reference
          "GS NFV-IFA011: Section 7.1.2, VNFD information element";
      }
      leaf provider {
        type string;
        mandatory true;
        description
          "Provider of the VNF and of the VNFD";
        reference
          "GS NFV-IFA011: Section 7.1.2, VNFD information element";
      }
      leaf product-name {
        type string;
        mandatory true;
        description
          "Name to identify the VNF Product. Invariant for the VNF 
           Product lifetime.";
        reference
          "GS NFV-IFA011: Section 7.1.2, VNFD information element";
      }
      leaf software-version {
        type string;
        mandatory true;
        description
          "Software version of the VNF. This is changed when there is
           any change to the software that is included in the VNF
           Package";
        reference
          "GS NFV-IFA011: Section 7.1.2, VNFD information element";
      }
      leaf version {
        type string;
        mandatory true;
        description
          "Identifies the version of the VNFD";
        reference
          "GS NFV-IFA011: Section 7.1.2, VNFD information element";
      }
      leaf product-info-name {
        type string;
        description
          "Human readable name of the VNFD. Can change
           during the VNF Product lifetime.";
        reference
          "GS NFV-IFA011: Section 7.1.2, VNFD information element";
      }
      leaf product-info-description {
        type string;
        description
          "Human readable description of the VNFD. Can change during
           the VNF Product lifetime.";
        reference
          "GS NFV-IFA011: Section 7.1.2, VNFD information element";
      }
      leaf-list vnfm-info {
        type string;
        min-elements 1;
        description
          "Identifies VNFM(s) compatible with the VNF described in
           this version of the VNFD.";
        reference
          "GS NFV-IFA011: Section 7.1.2, VNFD information element";
      }
      leaf localization-language {
        type string;
        description
          "Information about the language of the VNF.";
        reference
          "GS NFV-IFA011: Section 7.1.2, VNFD information element";
      }
      leaf default-localization-language {
        when "../localization-language";
        type string;
        description
          "Default localization language that is instantiated if no
           information about selected localization language is
           available. Shall be present if 'localization-language'
           is present and shall be absent otherwise.";
        reference
          "GS NFV-IFA011: Section 7.1.2, VNFD information element";
      }
      
      list vdu {
        key "id";
        min-elements 1;
        description
          "The Virtualisation Deployment Unit (VDU) is a construct supporting
           the description of the deployment and operational behaviour of a
           VNF component, or the entire VNF if it was not componentized in
           components.";
        reference
          "GS NFV IFA011: Section 7.1.6.2, VDU information element";
        leaf id {
          type string;
          description
            "Unique identifier of this VDU in VNFD.";
        }
        leaf name {
          type string;
          mandatory true;
          description
            "Human readable name of the VDU.";
          reference
            "GS NFV IFA011: Section 7.1.6.2.2";
        }
        leaf description {
          type string;
          description
            "Human readable description of the VDU.";
          reference
            "GS NFV IFA011: Section 7.1.6.2.2";
        }
        list int-cpd {
          key "id";
          min-elements 1;
          description
            "A internal-connection-point element is a type of
             connection point and describes network connectivity
             between a VDU instance and an internal Virtual Link or
             an external connection point.";
          reference
            "GS NFV IFA011: Section 7.1.6.4, VduCpd information
             element";
          choice cp-connection {
            mandatory true;
            description
              "A connection point must either connect to an internal
               virtual link or to an external connection points.";
            leaf int-virtual-link-desc {
              type leafref {
                path "../../../nfvo-rel2:virtual-link-descriptor/" +
                     "nfvo-rel2:id";
              }
              description
                "Connect to an internal VLD.";
            }
            leaf external-connection-point-descriptor {
              description
                "Connect to an external connection point";
              type leafref {
                path "../../../nfvo-rel2:" +
                     "external-connection-point-descriptor/" +
                     "nfvo-rel2:id";
              }
            }
          }
          leaf bitrate-requirement {
            type uint64;
            units "Mbps";
            description
              "Bitrate requirement on this CP.";
            reference
              "GS NFV IFA011: Section 7.1.6.4, VduCpd information
               element.";
          }
          uses virtual-network-interface-requirement;
          uses cpd;
        }
        leaf virtual-compute-desc {
          type leafref {
            path "../../nfvo-rel2:virtual-compute-descriptor/" +
                 "nfvo-rel2:id";
          }
          description
            "Describes CPU, Memory and acceleration requirements of
             the Virtualisation Container realizing this VDU.";
          reference
            "GS NFV IFA011: Section 7.1.6.2, VDU information
             element, and Section 7.1.9.2.2, VirtualComputeDesc
             information element.";
        }
        
        leaf-list virtual-storage-desc {
          type leafref {
            path "../../nfvo-rel2:virtual-storage-descriptor/" +
                 "nfvo-rel2:id";
          }
          description
            "Describes storage requirements for a VirtualStorage
             instance attached to the virtualisation container
             created from virtualComputeDesc defined for this VDU.";
          reference
            "GS NFV IFA011: Section 7.1.6.2, VDU information
             element, and Section 7.1.9.4, Information elements
             related to Virtual Storage.";
        }
        list boot-order {
          ordered-by user;
          key "virtual-storage-desc";
          leaf virtual-storage-desc {
            type leafref {
              path "../../nfvo-rel2:virtual-storage-desc";
            }
          }
        }
        container software-image-descriptor {
          presence
            "Can be used to specify image data if the VNF should be
             onboarded to the VIM by the NFVO";
          description
            "VM image data for the image used to boot the VDU.";
          reference
            "GS NFV IFA011: Section 7.1.6.5, SwImageDescriptor 
             information element";
          leaf name {
            type string;
            description
              "The name of this software image.";
            reference
              "GS NFV IFA011: Section 7.1.6.5 SwImageDescriptor
               information element.";
          }
          leaf version {
            type string;
            description
              "The version of this software image.";
            reference
              "GS NFV IFA011: Section 7.1.6.5 SwImageDescriptor
               information element.";            
          }
          leaf checksum {
            type string;
            description
              "The checksum of the software image file.";
            reference
              "GS NFV IFA011: Section 7.1.6.5 SwImageDescriptor
               information element.";            
          }
          leaf container-format {
            mandatory true;
            type enumeration {
              enum "aki" {
                description
                  "An Amazon kernel image.";
              }
              enum "ami" {
                description
                  "An Amazon machine image.";
              }
              enum "ari" {
                description
                  "An Amazon ramdisk image.";
              }
              enum "bare" {
                description
                  "The image does not have a container or metadata
                   envelope.";
              }
              enum "docker" {
                description
                  "A docker container format.";
              }
              enum "ova" {
                description
                  "An OVF package in a tarfile.";
              }
              enum "ovf" {
                description
                  "The OVF container format.";
              }
            }
            description
              "The container format describes the container file 
               format in which software image is provided.";
            reference
              "GS NFV IFA011: Section 7.1.6.5 SwImageDescriptor
               information element.";            
          }
          leaf disk-format {
            mandatory true;
            type enumeration {
              enum "aki" {
                description
                  "An Amazon kernel image.";
              }
              enum "ami" {
                description
                  "An Amazon machine image.";
              }
              enum "ari" {
                description
                  "An Amazon ramdisk image.";
              }
              enum "iso" {
                description
                  "An archive format for the data contents of an
                   disk, such as CD-ROM.";
              }
              enum "qcow2" {
                description
                  "Supported by the QEMU emulator that can expand 
                   dynamically and supports Copy on Write.";
              }
              enum "raw" {
                description
                "An unstructured disk image format; if you have a 
                 file without an extension it is possibly a raw 
                 format.";
              }
              enum "vdi" {
                description
                  "Supported by VirtualBox virtual machine monitor
                   and the QEMU emulator.";
              }
              enum "vhd" {
                description
                  "The VHD disk format, a common disk format used by
                   virtual machine monitors from VMware, Xen,
                   Microsoft, VirtualBox, and others.";
              }
              enum "vhdx" {
                description
                  "The VHDX disk format, an enhanced version of the
                   VHD format, which supports larger disk sizes among
                   other features.";
              }
              enum "vmdk" {
                description
                  "Common disk format supported by many common virtual
                   machine monitors.";
              }
            }
            description
              "The disk format of a software image is the format of
               the underlying disk image.";
          }
          leaf min-disk {
            type uint64;
            units "Gb";
            description
              "The minimal disk size requirement for this software
               image. The value of the 'size of storage' attribute
               of the VirtualStorageDesc referencing this
               SwImageDesc shall not be smaller than the value of
               minDisk.";
            reference
              "GS NFV IFA011: Section 7.1.6.5, SwImageDesc
               information element.";
          }
          leaf min-ram {
            type decimal64 {
              fraction-digits 1;
              range "0..max";
            }
            units "Gb";
            description
              "The minimal RAM requirement for this software image.
               The value of the 'size' attribute of VirtualMemoryData
               of the Vdu referencing this SwImageDesc shall not be
               smaller than the value of minRam.";
            reference
              "GS NFV IFA011: Section 7.1.6.5, SwImageDesc
               information element.";
          }
          leaf size {
            type uint64;
            description
              "The size of this software image.";
            reference
              "GS NFV IFA011: Section 7.1.6.5, SwImageDesc
               information element.";
          }
          leaf image {
            mandatory true;
            type inet:uri;
            description
              "This is a reference to the actual software image.
               The reference can be relative to the root of the VNF
               Package or can be a URL";
            reference
              "GS NFV IFA011: Section 7.1.6.5, SwImageDesc
               information element.";
          }
          leaf operating-system {
            type string;
            description
              "Identifies the operating system used in the software
               image. This attribute may also identify if a 32 bit or
               64 bit software image is used.";
            reference
              "GS NFV IFA011: Section 7.1.6.5, SwImageDesc
               information element.";
          }
          leaf-list supported-virtualization-environment {
            type string;
            description
              "Identifies the virtualisation environments
               (e.g. hypervisor) compatible with this software
               image.";
            reference
              "GS NFV IFA011: Section 7.1.6.5, SwImageDesc
               information element.";
          }
        }
        leaf-list nfvi-constraint {
          type string;
          description
            "Describes constraints on the NFVI for the VNFC
             instance(s) created from this Vdu. For example, aspects
             of a secure hosting environment for the VNFC instance
             that involve additional entities or processes.";
          reference
            "GS NFV IFA011: Section 7.1.6.2, VDU Information
             element.";
        }
        list monitoring-parameter {
          key "id";
          leaf id {
            type string;
            description
              "Unique identifier of the monitoring parameter.";
            reference
              "GS NFV IFA011: Section 7.1.11.3, MonitoringParameter
               information element.";
          }
          uses monitoring-parameter;
        }
        container configurable-properties {
        }
      }
      
      list virtual-compute-descriptor {
        key "id";
        description
          "Defines descriptors of virtual compute resources to be
           used by the VNF.";
        leaf id {
          type string;
          description
            "Unique identifier of this VirtualComputeDesc in the
             VNFD.";
          reference
            "GS NFV IFA011: Section 7.1.9.2, Information elements
             related to Virtual CPU.";
        }

        list request-additional-capability {
          key "name";
          leaf name {
            type string;
            description
              "Identifies a requested additional capability for the
               VDU. ETSI GS NFV-IFA 002 [i.1] describes acceleration
               capabilities.";
            reference
              "GS NFV IFA011: Section 7.1.9.5, 
               RequestedAdditionalCapabilityData Information
               element.";
          }
          leaf support-mandatory {
            type boolean;
            description
              "Indicates whether the requested additional capability
               is mandatory for successful operation.";
            reference
              "GS NFV IFA011: Section 7.1.9.5, 
               RequestedAdditionalCapabilityData Information
               element.";
          }

          leaf min-version {
            type string;
            description
              "Identifies the minimum version of the requested 
               additional capability.";
            reference
              "GS NFV IFA011: Section 7.1.9.5, 
               RequestedAdditionalCapabilityData Information
               element.";
          }

          leaf preferred-version {
            type string;
            description
              "Identifies the preferred version of the requested
               additional capability.";
            reference
              "GS NFV IFA011: Section 7.1.9.5, 
               RequestedAdditionalCapabilityData Information
               element.";
          }
          list target-performance-parameters {
            key "key";
            leaf key {
              type string;
            }
            leaf value {
              type string;
            }
            description
              "Identifies specific attributes, dependent on the 
               requested additional capability type.";
            reference
              "GS NFV IFA011: Section 7.1.9.5, 
               RequestedAdditionalCapabilityData Information
               element.";
          }
        }

        container virtual-memory {
          leaf size {
            type decimal64 {
              fraction-digits 1;
              range "0..max";
            }
            units "MB";
            mandatory true;
            description
              "Amount of virtual memory in MB.";
            reference
              "GS NFV IFA011: Section 7.1.9.3, Information elements
               related to Virtual Memory.";
          }
          leaf over-subscription-policy {
            type string;
            description
              "The memory core oversubscription policy in terms of 
               virtual memory to physical memory on the platform.
               The cardinality can be 0 during the allocation
               request, if no particular value is requested.";
            reference
              "GS NFV IFA011: Section 7.1.9.3, Information elements
               related to Virtual Memory.";
          }
          leaf numa-enabled {
            type boolean;
            description
              "It specifies the memory allocation to be cognisant of
               the relevant process/core allocation. The cardinality
               can be 0 during the allocation request, if no
               particular value is requested.";
            reference
              "GS NFV IFA011: Section 7.1.9.3, Information elements
               related to Virtual Memory.";
          }
          description
            "The virtual memory of the virtualised compute.";
        }
        
        container virtual-cpu {
          leaf cpu-architecture {
            type string;
            description
              "CPU architecture type. Examples are x86, ARM. The
               cardinality can be 0 during the allocation request,
               if no particular CPU architecture type is requested.";
            reference
              "GS NFV IFA011: Section 7.1.9.2.3, VirtualCpuData
               information elements.";
          }
          leaf number-of-virtual-cpus {
            type uint16 {
              range "1..max";
            }
            mandatory true;
            description
              "Number of virtual CPUs.";
            reference
              "GS NFV IFA011: Section 7.1.9.2.3, VirtualCpuData
               information elements.";
          }
          leaf clock {
            type uint32;
            units "MHz";
            description
              "Minimum virtual CPU clock rate (e.g. in MHz). The
               cardinality can be 0 during the allocation request,
               if no particular value is requested.";
            reference
              "GS NFV IFA011: Section 7.1.9.2.3, VirtualCpuData
               information elements.";
          }
          leaf oversubscription-policy {
            type string;
            description
              "The CPU core oversubscription policy e.g. the relation
               of virtual CPU cores to physical CPU cores/threads.
               The cardinality can be 0 during the allocation request,
               if no particular value is requested.";
            reference
              "GS NFV IFA011: Section 7.1.9.2.3, VirtualCpuData
               information elements.";
          }
          container virtual-cpu-pinning {
            presence "Set to specify CPU pinning.";
            leaf cpu-pinning-policy {
              mandatory true;
              type enumeration {
                enum "static";
                enum "dynamic";
              }
              description
                "Indicates the policy for CPU pinning. The policy can
                 take values of 'static' or 'dynamic'. The cardinality
                 can be 0 during the allocation request, if no
                 particular value is requested.";
            }
            container cpu-pinning-map {
              when "../nfvo-rel2:cpu-pinning-policy = 'static'";
            }
            description
              "If cpuPinningPolicy is defined as 'static', the
               cpuPinningMap provides the map of pinning virtual
               CPU cores to physical CPU cores/threads. Cardinality
               is 0 if cpuPinningPolicy has a different value than
               'static'.";
          }
          description
            "The virtual CPU pinning configuration for the
             virtualised compute resource.";
        }
      }
      
      list virtual-storage-descriptor {
        key "id";
        description
          "Storage requirements for a Virtual Storage instance
           attached to the VNFC created from this VDU";
        leaf id {
          type string;
          description
            "Unique identifier of this VirtualStorageDesc in the
             VNFD.";
          reference
            "GS NFV IFA011: Section 7.1.9.4, Information elements 
             related to Virtual Storage.";
        }

        leaf type-of-storage {
          // Needed to be able to onboard images
          type enumeration {
            enum "root";
            enum "swap";
            enum "ephemeral";
          }
          mandatory true;
          description
            "Type of virtualised storage resource (e.g. volume, 
             object).";
          reference
            "GS NFV IFA011: Section 7.1.9.4, Information elements 
             related to Virtual Storage.";
        }
        leaf size-of-storage {
          type uint64;
          units "GiB";
          mandatory true;
          description
            "Size of virtualised storage resource (e.g. size of
             volume, in GB)";
          reference
            "GS NFV IFA011: Section 7.1.9.4, Information elements 
             related to Virtual Storage.";
        }
        leaf rdma-enabled {
          type boolean;
          description
            "Indicate if the storage support RDMA.";
          reference
            "GS NFV IFA011: Section 7.1.9.4, Information elements 
             related to Virtual Storage.";
        }
        /*
          swImageDesc
          The specification prescribes a reference to a VDU's
          software image the VDU already has information of which 
          image it uses, so this would unnecessarily complicate things.
        */
      }
      
      list int-virtual-link-desc {
        key "id";
        description
          "Defines the virtualised resources monitoring parameters
           on VLD level.";
        reference
          "GS NFV IFA011: Section 7.1.7.2, VnfVirtualLinkDesc
          information element.";
        leaf id {
          type string;
          description
            "Unique identifier of this internal VLD in VNFD.";
          reference
            "GS NFV IFA011: Section 7.1.7, Information elements 
             related to the VLD.";
        }

        list desc-flavor {
          key "id";
          leaf id {
            type string;
            description
              "Identifies a flavour within a VnfVirtualLinkDesc.";
            reference
              "GS NFV IFA011: Section 7.1.8.5, VirtualLinkDescFlavor
               information element.";
          }
          uses link-bitrate-requirements;
          container qos {
            leaf latency {
              type uint32;
              units "ms";
              mandatory true;
              description
                "Specifies the maximum latency in ms.";
              reference
                "GS NFV IFA011: Section 7.1.8.10, QoS information
                 element.";
            }

            leaf packet-delay-variation {
              type uint32;
              units "ms";
              mandatory true;
              description
                "Specifies the maximum jitter in ms.";
              reference
                "GS NFV IFA011: Section 7.1.8.10, QoS information
                 element.";
            }

            leaf packet-loss-ratio {
              type decimal64 {
                fraction-digits "2";
                range "0..1.00";
              }
              description
                "Specifies the maximum packet loss ratio.";
              reference
                "GS NFV IFA011: Section 7.1.8.10, QoS information
                 element.";
            }
          }
          description
            "Describes a specific flavour of the VL with specific
             bitrate requirements.";
          reference
            "GS NFV IFA011: Section 7.1.7, Information elements 
             related to the VLD.";
        }
        
        uses connectivity-type;
        
        leaf-list test-access {
          type string;
          description
            "Specifies test access facilities expected on the VL
             (e.g. none, passive monitoring, or active (intrusive)
             loopbacks at endpoints.";
          reference
            "GS NFV IFA011: Section 7.1.7.2, VnfVirtualLinkDesc
             information element.";
        }
        leaf description {
          type string;
          description
            "Provides human-readable information on the purpose of
             the VL (e.g. control plane traffic).";
          reference
            "GS NFV IFA011: Section 7.1.7.2, VnfVirtualLinkDesc
             information element.";
        }
        list monitoring-parameter {
          key "id";
          leaf id {
            type string;
            description
              "Unique identifier of the monitoring parameter.";
          reference
            "GS NFV IFA011: Section 7.1.11.3, MonitoringParameter
             information element.";
          }
          uses monitoring-parameter;
        }
      }
      
      list ext-cpd {
        key "id";
        min-elements 1;

        description
          "Describes an external interface exposed by this VNF enabling
           connection with a Virual Link";
        reference
          "GS NFV IFA011: Section 7.1.2, VNFD information element.";
        
        leaf virtual-link-desc {
          description
            "Reference to the internal Virtual Link Descriptor (VLD)
             to which CPs instantiated from this external CP
             Descriptor (CPD) connect. Either intVirtualLinkDesc or
             intCpd shall be present.";
          type leafref {
            path "../../nfvo-rel2:virtual-link-descriptor/nfvo-rel2:id";
          }
        }
        /*
          intCpd
          we reference from the VDU's CP to the ext-CP instead of the
          ext-CP to the VDU's CP.
        */
        uses virtual-network-interface-requirement;
        uses cpd;
      }
      list deployment-flavor {
        must "nfvo-rel2:default-instantiation-level or " +
             "count(nfvo-rel2:instantiation-level) = 1";
        key "id";
        min-elements 1;
        description
          "Describes a specific Deployment Flavour (DF) of a VNF with
           specific requirements for capacity and performance.";
        reference
          "GS NFV IFA011: Section 7.1.2, VNFD information element.";
        leaf id {
          type string;
          description
            "Identifier of this DF within the VNFD.";
          reference
            "GS NFV IFA011: Section 7.1.8, Information elements
             to the DeploymentFlavor.";
        }
        leaf description {
          type string;
          description
            "Human readable description of the deployment flavor";
          reference
            "GS NFV IFA011: Section 7.1.8, Information elements
             to the DeploymentFlavor.";
        }
        list vdu-profile {
          key "id";
          min-elements 1;
          description
            "The Vduprofile describes additional instantiation data for
             a given VDU used in a deployment flavour.";
          reference
            "GS NFV IFA011: Section 7.1.8, Information elements
             to the DeploymentFlavor.";
          leaf id {
            type leafref {
              path "../../../nfvo-rel2:vdu/nfvo-rel2:id";
            }
            reference
              "GS NFV IFA011: Section 7.1.8.3, VduProfile information
               element.";
          }
          leaf min-number-of-instances {
            type uint16;
            mandatory true;
            description
              "Minimum number of instances of the VNFC based on this
               VDU that is permitted to exist for this flavour.";
            reference
              "GS NFV IFA011: Section 7.1.8.3, VduProfile information
               element.";
          }
          leaf max-number-of-instances {
            type uint16;
            mandatory true;
            must ". >= ../nfvo-rel2:min-number-of-instances";
            reference
              "GS NFV IFA011: Section 7.1.8.3, VduProfile information
               element.";
          }
          uses local-affinity-or-anti-affinity-rule;
          list affinity-or-anti-affinity-group-id {
            key "id";

            leaf id {
              type leafref {
                path "../../../" +
                     "nfvo-rel2:affinity-or-anti-affinity-group/" +
                     "nfvo-rel2:id";
              }
            }
            description
              "Identifier(s) of the affinity or anti-affinity
               group(s) the VDU belongs to.";
            reference
              "GS NFV IFA011: Section 7.1.8.3, VduProfile information
               element.";
          }
        }
        list virtual-link-profile {
          key "id flavor";
          description
            "Defines the internal VLD along with additional data which
             is used in this DF.";
          reference
            "GS NFV IFA011: Section 7.1.8.2, VnfDf information
             element.";

          leaf id {
            type leafref {
              path "../../../nfvo-rel2:virtual-link-descriptor/" +
                   "nfvo-rel2:id";
            }
            description
              "Uniquely identifies a Vnf VLD.";
            reference
              "GS NFV IFA011: Section 7.1.8.4, VirtualLinkProfile
               information element.";
          }
          leaf flavor {
            type leafref {
              path "deref(../nfvo-rel2:virtual-link-descriptor)" +
                   "/../nfvo-rel2:descriptor-flavor/nfvo-rel2:id";
            }
            description
              "Identifies a flavour within the VnfVirtualLinkDesc.";
            reference
              "GS NFV IFA011: Section 7.1.8.4, VirtualLinkProfile
               information element.";
          }
          uses local-affinity-or-anti-affinity-rule;
          list affinity-or-anti-affinity-group {
            key "id";
            leaf id {
              type leafref {
                path "../../../" +
                     "nfvo-rel2:affinity-or-anti-affinity-group/" +
                     "nfvo-rel2:id";
              }
            }
            description
              "Identifier(s) of the affinity or anti-affinity
               group(s) the VnfVirtualLinkDesc belongs to.";
            reference
              "GS NFV IFA011: Section 7.1.8.4, VirtualLinkProfile
               information element.";
          }
        }
        list instantiation-level {
          key "id";
          min-elements 1;
          description
            "Describes the various levels of resources that can be
             used to instantiate the VNF using this flavour.
             Examples: Small, Medium, Large. If there is only one
             'instantiationLevel' entry, it shall be treated as the
             default instantiation level for this DF.

             The InstantiationLevel information element describes a
             given level of resources to be instantiated within a
             deployment flavour in term of the number of VNFC instances
             to be created from each VDU.
             All the VDUs referenced in the level shall be part of the
             corresponding deployment flavour and their number shall
             be within the range (min/max) for this deployment flavour.";
          reference
            "GS NFV IFA011: Section 7.1.8.2 VnfDf information element";
          leaf id {
            type string;
            description
              "Uniquely identifies a level with the DF.";
            reference
              "GS NFV IFA011: Section 7.1.8.7 InstantiationLevel
               information element";
          }
          leaf description {
            type string;
            description
              "Human readable description of the instantiation level";
            reference
              "GS NFV IFA011: Section 7.1.8.7 InstantiationLevel
               information element";
          }
          list vdu-level {
            key "id";
            min-elements 1;
            description
              "Sets the number of instances for the VDU in this
               instantiation level.";
            reference
              "GS NFV IFA011: Section 7.1.8.7 InstantiationLevel
               information element";
            leaf id {
              type leafref {
                path "../../../../nfvo-rel2:vdu/nfvo-rel2:id";
              }
              description
                "Uniquely identifies a VDU.";
              reference
                "GS NFV IFA011: Section 7.1.8.9 VduLevel information
                 element";
            }
            leaf number-of-instances {
              type uint16;
              must ". <= ../../../" +
                   "nfvo-rel2:vdu-profile[vdu=current()/../" +
                   "nfvo-rel2:vdu]/nfvo-rel2:max-number-of-instances";
              must ". >= ../../../" +
                   "nfvo-rel2:vdu-profile[vdu=current()/../" +
                   "nfvo-rel2:vdu]/nfvo-rel2:min-number-of-instances";
              mandatory true;
              description
                "Number of instances of VNFC based on this VDU to
                 deploy for this level.";
              reference
                "GS NFV IFA011: Section 7.1.8.9 VduLevel information
                 element";
            }
          }
          list scaling-info {
            key "id";
            description
              "The InstantiationLevel information element describes a
               given level of resources to be instantiated within a
               DF in term of the number of VNFC instances to be 
               created from each VDU.";
            reference
              "GS NFV IFA011: Section 7.1.8.7 InstantiationLevel
               information element";
            leaf id {
              type leafref {
                path "../../../nfvo-rel2:scaling-aspect/nfvo-rel2:id";
              }
              description
                "Identifier of the scaling aspect.";
              reference
                "GS NFV IFA011: Section 7.1.8.8 ScaleInfo information
                 element";
            }
            leaf scale-level {
              type uint32;
              description
                "The scale level, greater than or equal to 0.";
              reference
                "GS NFV IFA011: Section 7.1.8.8 ScaleInfo information
                 element";
            }
          }
        }
        leaf default-instantiation-level {
          type leafref {
            path "../nfvo-rel2:instantiation-level/nfvo-rel2:id";
          }
          description
            "This attribute references the 'instantiationLevel'
             entry which defines the default instantiation level for
             this DF. It shall be present if there are multiple
             'instantiationLevel' entries.";
          reference
            "GS NFV IFA011: Section 7.1.8.2 VnfDf information
                 element";
        }
        leaf-list supported-operation {
          type identityref {
            base supported-operation;
          }
          description
            "Indicates which operations are available for this DF via
             the VNF LCM interface. Instantiate VNF, Query VNF and
             Terminate VNF are supported in all DF and therefore
             need not be included in this list.";
          reference
            "GS NFV IFA011: Section 7.1.8.2 VnfDf information
                 element";
        }
        container lcm-operations-configuration {
          description
            "This information element is a container for all
             attributes that affect the invocation of the VNF
             Lifecycle Management operations, structured by
             operation.";
          reference
            "GS NFV IFA011: Section 7.1.8.2 VnfDf information
             element";
          
          leaf instantiate-vnf-op-config {
            type string;
            description
              "Configuration parameters for the InstantiateVnf
               operation.";
            reference
              "GS NFV IFA011: Section 7.1.5.2
               VnfLcmOperationsConfiguration information element";
          }
          container scale-vnf-op-config {
            description
              "Configuration parameters for the ScaleVnf operation.";
            reference
              "GS NFV IFA011: Section 7.1.5.2
               VnfLcmOperationsConfiguration information element";

            leaf parameter {
              type string;
              description
                "VNF-specific parameter to be passed when invoking
                 the ScaleVnf operation.";
              reference
                "GS NFV IFA011: Section 7.1.5.4
                 ScaleVnfOpConfig information element";
            }
            leaf scaling-by-more-than-one-step-supported {
              type boolean;
              default false;
              description
                "Signals whether passing a value larger than one in
                 the numScalingSteps parameter of the ScaleVnf
                 operation is supported by this VNF.
                 Default is FALSE, i.e. 'not supported'.";
              reference
                "GS NFV IFA011: Section 7.1.5.4
                 ScaleVnfOpConfig information element";
            }
          }
          container scale-vnf-to-level-op-config {
            description
              "This information element defines attributes that 
               affect the invocation of the ScaleVnfToLevel
               operation.";
            reference
              "GS NFV IFA011: Section 7.1.5.2
               VnfLcmOperationsConfiguration information element";

            leaf parameter {
              type string;
              description
                "VNF-specific parameter to be passed when invoking
                 the ScaleVnfToLevel operation.";
              reference
                "GS NFV IFA011: Section 7.1.5.5
                 ScaleVnfToLevelOpConfig information element";
            }
            leaf arbitrary-target-levels-supported {
              type boolean;
              description
                "Signals whether scaling according to the parameter
                 'scaleInfo' is supported by this VNF.";
              reference
                "GS NFV IFA011: Section 7.1.5.5
                 ScaleVnfToLevelOpConfig information element";
            }
          }
          container heal-vnf-op-config {
            description
              "This information element defines attributes that
               affect the invocation of the HealVnf operation.";
            reference
              "GS NFV IFA011: Section 7.1.5.2
               VnfLcmOperationsConfiguration information element";

            leaf parameter {
              type string;
              description
                "VNF-specific parameter to be passed when invoking
                 the HealVnf operation.";
              reference
                "GS NFV IFA011: Section 7.1.5.6 HealVnfOpConfig
                 information element";
            }
            leaf cause {
              type string;
              description
                "Supported 'cause' parameter values.";
              reference
                "GS NFV IFA011: Section 7.1.5.6 HealVnfOpConfig
                 information element";
            }
          }
          container terminate-vnf-op-config {
            description
              "This information element defines attributes that 
               affect the invocation of the TerminateVnf operation.";
            reference
              "GS NFV IFA011: Section 7.1.5.2
               VnfLcmOperationsConfiguration information element";
            leaf min-graceful-termination {
              type yang:timeticks;
              description
                "Minimum timeout value for graceful termination of
                 a VNF instance.";
              reference
                "GS NFV IFA011: Section 7.1.5.7
                 TerminateVnfOpConfig information element";
            }
            leaf max-recommended-graceful-termination {
              type yang:timeticks;
              description
                "Maximum recommended timeout value that can be needed
                 to gracefully terminate a VNF instance of a
                 particular type under certain conditions, such as
                 maximum load condition. This is provided by VNF
                 provider as information for the operator
                 facilitating the selection of optimal timeout value.
                 This value is not used as constraint.";
              reference
                "GS NFV IFA011: Section 7.1.5.7
                 TerminateVnfOpConfig information element";
            }
          }
          container operate-vnf-op-config {
            description
              "This information element defines attributes that 
               affect the invocation of the OperateVnf operation.";
            reference
              "GS NFV IFA011: Section 7.1.5.2
               VnfLcmOperationsConfiguration information element";

            leaf min-graceful-stop-timeout {
              type yang:timeticks;
              description
                "Minimum timeout value for graceful stop of a VNF
                 instance.";
              reference
                "GS NFV IFA011: Section 7.1.5.8
                 OperateVnfOpConfig information element";
            }
            leaf max-recommended-graceful-stop-timeout {
              type yang:timeticks;
              description
                "Maximum recommended timeout value that can be 
                 needed to gracefully stop a VNF instance of a
                 particular type under certain conditions, such as
                 maximum load condition. This is provided by VNF
                 provider as information for the operator facilitating
                 the selection of optimal timeout value. This value
                 is not used as constraint.";
              reference
                "GS NFV IFA011: Section 7.1.5.8
                 OperateVnfOpConfig information element";
            }
          }
        }
        list affinity-or-anti-affinity-group {
          key "id";

          leaf id {
            type string;
          }

          leaf affinity-type {
            mandatory true;
            type affinity-type;
          }

          leaf affinity-scope {
            mandatory true;
            type affinity-scope;
          }
        }
        list monitoring-parameter {
          key "id";
          leaf id {
            type string;
          }
          uses monitoring-parameter;
        }
        list scaling-aspect {
          key "id";
          leaf id {
            type string;
          }
          leaf name {
            type string;
          }
          leaf description {
            type string;
          }
          leaf associated-group {
            type leafref {
              path "../../../nfvo-rel2:element-group/nfvo-rel2:id";
            }
          }
          leaf max-scale-level {
            type uint32 {
              range "1..max";
            }
          }
        }
      }
      container configurable-properties {
        leaf auto-scalable {
          type empty;
        }
        leaf auto-healable {
          type empty;
        }
        leaf-list additional-configurable-property {
          type string;
        }
      }
      container modifiable-attributes {
        leaf-list extension {
          type string;
        }
        leaf-list metadata {
          type string;
        }
      }
      list lifecycle-management-script {
        key "event";
        leaf event {
          type string;
        }
        leaf script {
          type string;
        }
      }
      list element-group {
        key "id";
        leaf id {
          type string;
        }
        leaf description {
          type string;
        }
        leaf-list vdu {
          type leafref {
            path "../../nfvo-rel2:vdu/nfvo-rel2:id";
          }
        }
        leaf-list virtual-link-descriptor {
          type leafref {
            path "../../nfvo-rel2:virtual-link-descriptor/nfvo-rel2:id";
          }
        }
      }
      list indicator {
        key "id";
        leaf id {
          type string;
        }
        leaf name {
          type string;
        }
        leaf-list indicator-value {
          type string;
        }
        leaf source {
          type enumeration {
            enum "VNF";
            enum "EM";
            enum "both";
          }
        }
      }
      leaf-list auto-scale {
        type string;
      }
    }
  }
}
