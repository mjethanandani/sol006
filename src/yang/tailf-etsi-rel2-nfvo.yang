module tailf-etsi-rel2-nfvo {
  namespace "http://tail-f.com/pkg/tailf-etsi-rel2-nfvo";
  prefix nfvo-rel2;

  include tailf-etsi-rel2-nfvo-common {
    revision-date "2017-01-20";
  }
  include tailf-etsi-rel2-nfvo-ns {
    revision-date "2017-01-20";
  }
  include tailf-etsi-rel2-nfvo-vnf;

  organization
    "European Telecommunications Standards Institute (ETSI)";

  description
    "Network Function Virtualization Orchestrator";

  revision 2017-01-20 {
    description
      "Initial revision.
       NSD according to ETSI GS NFV-IFA 014 V2.1.1 (2016-10)
       VNFD according to ETSI GS NFV-IFA 011 V2.1.1 (2016-10)
      ";
  }

  container nfvo {
    uses vnfd;
    uses nsd;

    container vnf-info {}
    container nsr {}
    container ns-info {}

    container onboarding {}

    container settings {}
 } // nfvo
}
