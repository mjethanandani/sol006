module etsi-nfvo {
  namespace "urn:etsi:params:xml:ns:yang:etsi-nfvo";
  prefix nfvo;

  include etsi-nfvo-common;
  include etsi-nfvo-vnf;
  include etsi-nfvo-ns;

  organization
    "European Telecommunications Standards Institute (ETSI)";

  description
    "Network Function Virtualization Orchestrator";

  revision 2017-01-20 {
    description
      "Initial revision.
       NSD according to ETSI GS NFV-IFA 014 V2.1.1 (2016-10)
       VNFD according to ETSI GS NFV-IFA 011 V2.1.1 (2016-10)";
  }

  container nfvo {
    uses vnfd;
    uses nsd;

    container vnf-info {}
    container nsr {}
    container ns-info {}

    container onboarding {}

    container settings {}
 } // nfvo
}
